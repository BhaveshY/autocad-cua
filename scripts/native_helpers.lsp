; Small AutoCAD 2019 primitives. No layout or task template.
(defun acua:init (/ font ts)
 (vl-load-com)
 (setq acua:doc (vla-get-ActiveDocument (vlax-get-acad-object)) acua:ms (vla-get-ModelSpace acua:doc) acua:handles nil)
 (setq font (findfile (strcat (getenv "WINDIR") "/Fonts/arial.ttf")))
 (if (not font) (setq font (findfile "simplex.shx")))
 (if (not font) (progn (princ "No supported font found") (exit)))
 (setq ts (if (tblsearch "STYLE" "Cua-Text") (vla-item (vla-get-TextStyles acua:doc) "Cua-Text") (vla-add (vla-get-TextStyles acua:doc) "Cua-Text")))
 (vla-put-FontFile ts font) (vla-put-Height ts 0.0) (vla-put-Width ts 1.0)
 (setvar "CLAYER" "0")
 (list font (vla-get-Count acua:ms)))
(defun acua:layer (name color weight / l)
 (setq l (if (tblsearch "LAYER" name) (vla-item (vla-get-Layers acua:doc) name) (vla-add (vla-get-Layers acua:doc) name)))
 (if (/= (getvar "CLAYER") name) (vla-put-Freeze l :vlax-false))
 (vla-put-LayerOn l :vlax-true) (vla-put-Lock l :vlax-false)
 (vla-put-Color l color) (vla-put-Lineweight l weight))
(defun acua:clear-model (/ l objects e)
 (vlax-for l (vla-get-Layers acua:doc) (vla-put-Lock l :vlax-false))
 (vlax-for e acua:ms (setq objects (cons e objects)))
 (foreach e objects (vla-Delete e)))
(defun acua:remember (e / h)
 (if (not e) (progn (princ "Entity creation failed") (exit)))
 (setq h (cdr (assoc 5 (entget e))) acua:handles (cons h acua:handles)) h)
(defun acua:poly (points layer closed)
 (acua:remember (entmakex (append (list '(0 . "LWPOLYLINE") '(100 . "AcDbEntity") (cons 8 layer) '(100 . "AcDbPolyline") (cons 90 (length points)) (cons 70 (if closed 1 0))) (mapcar '(lambda (p) (cons 10 p)) points)))))
(defun acua:rect (x y w h layer)
 (acua:poly (list (list x y) (list (+ x w) y) (list (+ x w) (+ y h)) (list x (+ y h))) layer T))
(defun acua:line (p q layer)
 (acua:remember (entmakex (list '(0 . "LINE") (cons 8 layer) (cons 10 p) (cons 11 q)))))
(defun acua:text (p height value layer centered / data)
 (setq data (list '(0 . "TEXT") (cons 8 layer) (cons 10 p) (cons 40 height) (cons 1 value) '(7 . "Cua-Text")))
 (if centered (setq data (append data (list '(72 . 1) '(73 . 2) (cons 11 p)))))
 (acua:remember (entmakex data)))
(defun acua:arc (p radius start end layer)
 (acua:remember (entmakex (list '(0 . "ARC") (cons 8 layer) (cons 10 p) (cons 40 radius) (cons 50 start) (cons 51 end)))))
(defun acua:circle (p radius layer)
 (acua:remember (entmakex (list '(0 . "CIRCLE") (cons 8 layer) (cons 10 p) (cons 40 radius)))))
(defun acua:dim (p q location angle height layer / d)
 (setq d (vla-AddDimRotated acua:ms (vlax-3d-point p) (vlax-3d-point q) (vlax-3d-point location) angle))
 (vla-put-Layer d layer) (vla-put-TextStyle d "Cua-Text") (vla-put-TextHeight d height)
 (vla-put-ArrowheadSize d (* height 0.7)) (vla-put-ScaleFactor d 1.0) (vla-put-PrimaryUnitsPrecision d 0)
 (vla-Update d) (acua:remember (vlax-vla-object->ename d)))
(defun acua:plot (path media low high scale / layout a b)
 (setq layout (vla-get-ActiveLayout acua:doc))
 (vla-put-ConfigName layout "DWG To PDF.pc3") (vla-RefreshPlotDeviceInfo layout)
 (vla-put-CanonicalMediaName layout media) (vla-put-PaperUnits layout 1) (vla-put-PlotRotation layout 0)
 (setq a (vlax-make-safearray vlax-vbDouble '(0 . 1)) b (vlax-make-safearray vlax-vbDouble '(0 . 1)))
 (vlax-safearray-fill a low) (vlax-safearray-fill b high) (vla-SetWindowToPlot layout a b)
 (vla-put-PlotType layout 4) (vla-put-UseStandardScale layout :vlax-false) (vla-SetCustomScale layout 1.0 scale)
 (vla-put-CenterPlot layout :vlax-true) (vla-put-StyleSheet layout "monochrome.ctb")
 (vla-put-PlotWithPlotStyles layout :vlax-true) (vla-put-PlotWithLineweights layout :vlax-true)
 (setvar "BACKGROUNDPLOT" 0) (vla-put-QuietErrorMode (vla-get-Plot acua:doc) :vlax-true)
 (vla-PlotToFile (vla-get-Plot acua:doc) path))
(defun acua:finish (/ s)
 (setq s "")
 (foreach h (reverse acua:handles) (setq s (strcat s (if (= s "") "" ",") "\"" h "\"")))
 (strcat "{\"model_space_count\":" (itoa (vla-get-Count acua:ms)) ",\"handles\":[" s "]}"))
